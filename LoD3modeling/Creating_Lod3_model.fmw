FME workspace Creating_Lod3_model.fmw

Parameters:
- SourceDataset_CITYGML = D:\projects\TUMbldExplore\datasets\raw\CityGML\TUM Munich\TUM Munich.gml   # Source CityGML File(s)
- bldSelect = DEBY_LOD2_4959323   # Select building ID
- SourceDataset_SKP = D:\projects\SemanticConflictDetection\inputCAD\rectangularWindow\rectangularWindow.skp   # Source Trimble SketchUp File
- DestDataset_CITYGML = D:\projects\PointCloud_Image_fusion\data\resultLoD3\wallC\tumLoD3bld.gml   # Destination CityGML Document
- SourceDataset_CITYGML_5 = D:\projects\PointCloud_Image_fusion\data\extracted3Dshapes\3dExactShapes\3dExactShapesWallC.gml   # Source CityGML File(s)

Readers:
- CITYGML_1: CITYGML from $(SourceDataset_CITYGML)
- SKP_1: SKP from $(SourceDataset_SKP)
- CITYGML_2: CITYGML from $(SourceDataset_CITYGML_5)

Writers:
- CITYGML_3: CITYGML to $(DestDataset_CITYGML)

Bookmark: input CAD models
rectangularWindow (reader SKP_1)
    -> Junction_73
    -> rectangularWindow

Bookmark: input LoD3 window
Note: CityGML Windows
Junction_73
    -> openingClassAssign_2
Note: assign respective class to match window types
openingClassAssign_2: AttributeCreator
    ATTR_TABLE:
      SET_TO openingClass = RectangleWindow
      SET_TO window = window
    -> tmpID_2
tmpID_2: AttributeCreator
    ATTR_TABLE = SET_TO tmpID = 0
    -> FeatureMerger_2 [SUPPLIER]
Note: count of windows and openingID2
Junction_15
    -> GeometryRemover_3
GeometryRemover_3
    -> AttributeKeeper_3
AttributeKeeper_3
    CREATE_BULK_MODE_FEATURES = NO
    KEEP_ATTRS = openingClass,windowWidthAtt,openingID2,tmpID
    -> tmpID_3
tmpID_3: AttributeCreator
    ATTR_TABLE = SET_TO tmpID = 0
    -> FeatureMerger_2 [REQUESTOR]
Note: make as many window duplicates as there are windows
FeatureMerger_2
    ATTR_ACCUM_MODE = Merge Supplier
    ATTR_CONFLICT_RES = Use Requestor
    IGNORE_NULLS = No
    JOIN_KEYS = @Value(tmpID) @Value(tmpID) AUTO
    MERGE_TYPE = Attributes and Geometry
    PROCESS_DUPS = NO
    REJECT_NULL_MISSING_KEYS = No
    SUPPLIERS_FIRST = No
    MERGED -> BoundsFitter [Observed]

Bookmark: 1 INPUT
rectangularWindow: Inspector

Bookmark: 3D shapes
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer
GenericCityObject (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, _angle xml_buffer, _xFirst xml_buffer, _yFirst xml_buffer, openingID2 xml_buffer
    -> AttributeCreator

Bookmark: 2 SYSTEM
AttributeCreator
    ATTR_TABLE = SET_TO windowWidthAtt = 0.1
    -> Junction
    -> Rotator
Junction
    -> GeometryRemover
    -> ExpressionEvaluator_2
Note: pass all IDs
GeometryRemover
    -> Junction_15
Note: windows positioned at the facade
Note: 3D raw building geometry
Junction_2
    -> AttributeKeeper_10
Note: Facade with holes for openings
Junction_21
    -> Junction_33
Note: TestFilter : rest of walls
Junction_39
    -> CityGMLSemSetter_2
Note: Split2parts : GroundSurface
Junction_37
    -> CityGMLSemSetter_2
Note: Split2parts : RoofSurface
Junction_43
    -> CityGMLSemSetter_2
Note: Split2parts : Address
Junction_45
    -> CityGMLSemSetter_2
CityGMLSemSetter_2: TestFilter
    DEFAULT_VALUE = <UNFILTERED>
    TEST_LIST = "BOOL_OP,OR,COMPOSITE_TEST,""""""1"""""",TEST_CLAUSE,TEST @Value(fme_feature_type) = Address",Address,"BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = RoofSurface",RoofSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(openingClass) = RectangleWindow",Window,"BOOL_OP,OR,COMPOSITE_TEST,""""""1"""""",TEST_CLAUSE,TEST @Value(fme_feature_type) = Building",Building,"BOOL_OP,OR,COMPOSITE_TEST,""""""1"""""",TEST_CLAUSE,TEST @Value(openingClass) = RectangleDoor",Door
    GroundSurface -> GroundSurface (writer CITYGML_3)
    RoofSurface -> RoofSurface (writer CITYGML_3)
    WallSurface -> WallSurface (writer CITYGML_3)
    Window -> Window (writer CITYGML_3)
    Building -> Building (writer CITYGML_3)
    Door -> Door (writer CITYGML_3)

Bookmark: set correct orientation for fitting -> bboxes oriented
Note: apply global rotation, rot. vertex is beg. of wall / -> otherwise you fit not to Oriented BBOx
Rotator
    ANGLE = -@Value(_angle)
    XORIG = @Value(_xFirst)
    YORIG = @Value(_yFirst)
    ROTATED -> Offsetter_2
Note: refine to align to the surface
Offsetter_2
    MODE = Cartesian Coordinate
    XOFF = 0
    YOFF = @Value(windowWidthAtt)
    ZOFF = 0
    OFFSET -> BoundsFitter [Control]
    OFFSET -> FeatureMerger_14 [SUPPLIER]
Note: actual fitting
BoundsFitter
    GROUP_BY = openingID2
    MODE = 3D
    ORDERED = No
    ORDERED_2 = No
    Corrected -> FeatureMerger_14 [REQUESTOR]
Note: somehow BoundsFitter deltes input attributes - one need the 3D affine matrix to get back to the origin
FeatureMerger_14
    ATTR_ACCUM_MODE = Merge Supplier
    ATTR_CONFLICT_RES = Use Supplier
    IGNORE_NULLS = No
    JOIN_KEYS = @Value(openingID2) @Value(openingID2) AUTO
    MERGE_TYPE = Attributes Only
    PROCESS_DUPS = NO
    REJECT_NULL_MISSING_KEYS = No
    SUPPLIERS_FIRST = No
    MERGED -> Rotator_3
Note: apply global rotation, rot. vertex is beg. of wall
Rotator_3
    ANGLE = @Value(_angle)
    XORIG = @Value(_xFirst)
    YORIG = @Value(_yFirst)
    ROTATED -> Junction_2

Bookmark: Windows as CityGML opening features
Note: set up window's: / -unique ID / -parent ID of a opennig -> wall -> building ->
Note: clean attributes
AttributeKeeper_10
    CREATE_BULK_MODE_FEATURES = NO
    KEEP_ATTRS = gml_parent_id,openingClass,window,openingID2,gml_id
    -> AttributeCreator_3
Note: re-assign gml_id as a parent id: it'll point to the wall
AttributeCreator_3
    ATTR_TABLE = SET_TO gml_parent_id = @Value(gml_id)
    -> UUIDGenerator_2
Note: set up unique id per each opening
UUIDGenerator_2
    UUID_ATTR = uuid
    -> StringConcatenator_2
StringConcatenator_2
    ACTION = Create New Attribute
    PARM_LINE = fme_basicstring:14%18%1%12:@Value(window)@Value(openingID2)-@Value(uuid)
    VAL_ATTR = gml_id
    -> Deaggregator_5
Deaggregator_5
    EXPLODE_INSTANCES = No
    GEOM_NAME_FIELD = _geometry_name
    LIST_ATTR_MODE_LOOKUP = LEAN
    MODE = Flatten All Levels
    SPLIT_COMPOSITES = Yes
    DEAGGREGATED -> GeometryInstantiator
Note: remove instatiation of cad models
GeometryInstantiator
    INSTANTIATED -> Deaggregator_6
Deaggregator_6
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryPropertyRemover
GeometryPropertyRemover
    REMOVETYPE_PARAM = Traits
    REMOVE_ALL = Yes
    REMOVED -> CityGMLGeometrySetter_4
Note: set opennig as boundedBy
CityGMLGeometrySetter_4
    GEOM = lod3MultiSurface
    ROLE = opening
    -> AttributeCreator_2
Note: fake attr. for feature type to avoid self-assigning
AttributeCreator_2
    ATTR_TABLE = SET_TO fme_feature_type = wind
    -> CoordinateSystemSetter
CoordinateSystemSetter
    COORDSYS = ETRS89.UTM-32N
    -> CityGMLSemSetter_2

Bookmark: 3d shapes to 2d shapes
Note: obtain rightAngle
ExpressionEvaluator_2
    ACTION = Create New Attribute
    EXPRESSION = @sub(360,@Value(_angle))
    VAL_ATTR = rightAngle
    -> Rotator_2

Bookmark: set up quasi-2D crs
Rotator_2
    ANGLE = @Value(rightAngle)
    XORIG = @Value(_xFirst)
    YORIG = @Value(_yFirst)
    ROTATED -> CoordinateSwapper_2
Note: y to Z
CoordinateSwapper_2
    SWAP_TYPE = Y <-> Z
    -> 2DForcer_3

Bookmark: Find correct 2D projection, angle alignment
2DForcer_3
    2D -> BoundingBoxReplacer
tmpID_4: Counter
    CNT_ATTR = _count
    DOMAIN = counter
    SCOPE = Local
    START = 0
    -> FeatureMerger_6 [SUPPLIER]
tmpID_5: Counter
    CNT_ATTR = _count
    DOMAIN = counter
    SCOPE = Local
    START = 0
    -> FeatureMerger_6 [REQUESTOR]
FeatureMerger_6
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> ExpressionEvaluator_3
Note: borders of rasterized facade
Note: obtain rightAngle
ExpressionEvaluator_3
    ACTION = Create New Attribute
    EXPRESSION = @sub(360,@Value(_angle))
    VAL_ATTR = rightAngle
    -> Junction_76
Note: cut facade by openings
Junction_76
    -> Junction_77

Bookmark: Cut holes for openings in facade
BoundingBoxReplacer
    BOXTYPE = 2D Bounding Box
    BOX -> Clipper_2 [CLIPPER]
Note: raw facade
Junction_77
    -> Rotator_13
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> DonutBridgeBuilder_2
DonutBridgeBuilder_2
    -> CoordinateSwapper_11
Note: y to Z
CoordinateSwapper_11
    SWAP_TYPE = Y <-> Z
    -> 3DAffiner_6
Note: get back the correct global X,Y
3DAffiner_6
    A = 1
    B = 0
    C = 0
    D = 0
    E = 0
    F = 1
    G = 0
    H = @Value(_yFirst)
    I = 0
    J = 0
    K = 1
    L = 0
    AFFINED -> Rotator_14
Note: Set orientation of the raw facade
Rotator_14
    ANGLE = @Value(_angle)
    XORIG = @Value(_xFirst)
    YORIG = @Value(_yFirst)
    ROTATED -> Junction_21

Bookmark: given city model
Address (reader CITYGML_1)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer
    -> Reprojector
CityModel (reader CITYGML_1)
    attributes: citygml_target_uri xml_buffer, gml_description xml_buffer, gml_name xml_buffer, citygml_city_object_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Reprojector
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer
    -> Reprojector
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Reprojector

Bookmark: pick the building
Note: to ETRS89
Reprojector
    DEST = ETRS89.UTM-32N
    INTERPOLATION_TYPE_NAME = Nearest Neighbor
    RASTER_CELL_SIZE = Preserve Cells
    RASTER_TOLERANCE = 0.0
    SOURCE = Read from feature
    REPROJECTED -> Decider_3
Decider_3: TestFilter
    DEFAULT_VALUE = <UNFILTERED>
    TEST_LIST:
      "BOOL_OP,OR,COMPOSITE_TEST,""""""1 OR 2"""""",TEST_CLAUSE,TEST @Value(gml_id) = $(bldSelect)
      TEST @Value(gml_parent_id) = $(bldSelect)",$(bldSelect)
    $(bldSelect) -> Split2parts
Split2parts: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(fme_feature_type) = Building",Building,"BOOL_OP,OR,COMPOSITE_TEST,""""""1"""""",TEST_CLAUSE,TEST @Value(fme_feature_type) = RoofSurface",Roof,"BOOL_OP,OR,COMPOSITE_TEST,""""""1"""""",TEST_CLAUSE,TEST @Value(fme_feature_type) = Address",Address
    GroundSurface -> Junction_37
    WallSurface -> TestFilter_11
    Building -> Junction_18
    Roof -> Junction_43
    Address -> Junction_45

Bookmark: windows and upgraded walls as CityGML LoD3
Junction_18
    -> CityGMLSemSetter_2
    -> GeometryRemover_2

Bookmark: set citymodel
GeometryRemover_2
    -> AttributeKeeper_7
AttributeKeeper_7
    CREATE_BULK_MODE_FEATURES = NO
    KEEP_ATTRS = gml_parent_id
    -> AttributeRenamer_2
AttributeRenamer_2
    ATTR_TABLE = RENAME_SET_DEFAULT gml_parent_id > gml_id
    -> CityModel (writer CITYGML_3)

Bookmark: CityGML
CityModel (writer CITYGML_3)
    attributes: citygml_target_uri xml_buffer, gml_description xml_buffer, gml_name xml_buffer, citygml_city_object_member{}.xlink_href xml_buffer, citygml_appearance_member{}.xlink_href xml_buffer, gml_feature_member{}.xlink_href xml_buffer
Building (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer
Door (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_address{}.xlink_href xml_buffer
GroundSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
RoofSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
WallSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
Window (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer
Note: CityModel
Junction_49

Bookmark: cut within the facade range
Note: facade of interest
TestFilter_11
    DEFAULT_VALUE = <UNFILTERED>
    TEST_LIST = "BOOL_OP,OR,COMPOSITE_TEST,""""""1"""""",TEST_CLAUSE,TEST @Value(gml_id) = DEBY_LOD2_4959323_652151f9-f41e-404f-97d3-19b720adc35f",DEBY_LOD2_4959323_652151f9-f41e-404f-97d3-19b720adc35f
    DEBY_LOD2_4959323_652151f9-f41e-404f-97d3-19b720adc35f -> Aggregator_6
    <UNFILTERED> -> Junction_39
Aggregator_6
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> BoundsExtractor_6
    AGGREGATE -> tmpID_5

Bookmark: Select lowest line of the facade and calculate orientation and XYZ position
BoundsExtractor_6
    ZMAX = maxHeight
    ZMIN = minHeight
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryPartExtractor
GeometryPartExtractor
    GQUERY:
      for $geom in //geometry
      where $geom/@fme_geometry_type = 'IFMELine'
      return number($geom/@fme_id)
    EXTRACTED -> Chopper_2
Chopper_2
    DEAGGREGATE_INPUT = Deaggregate
    MAX_VERTICES = 2
    MODE = By Vertex
    REMNANT_ATTR = _remnant
    CHOPPED -> BoundsExtractor_5
Note: select lowest line
BoundsExtractor_5
    ZMAX = LineH
    -> TestFilter_3
TestFilter_3
    DEFAULT_VALUE = <UNFILTERED>
    TEST_LIST:
      "BOOL_OP,AND,COMPOSITE_TEST,""""""1 AND 2"""""",TEST_CLAUSE,TEST @Value(LineH) >= @sub(@Value(minHeight),0.5)
      TEST @Value(LineH) <= @sum(@Value(minHeight),0.5)",lowestLine
    lowestLine -> 2DForcer_5
2DForcer_5
    2D -> LineCombiner_2
LineCombiner_2
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> HorizontalAngleCalculator_3
Note: tmpID_6 : Input
Junction_53

Bookmark: angle and reference coordinates extract
Note: angle
HorizontalAngleCalculator_3
    ANGLE_TYPE = Feature
    UNIT_OUTPUT = DEG
    -> CoordinateExtractor
Note: first
CoordinateExtractor
    IND = 0
    MODE = Specify Coordinate
    X_ATTR = _xFirst
    Y_ATTR = _yFirst
    -> CoordinateExtractor_2
Note: last
CoordinateExtractor_2
    IND = -1
    MODE = Specify Coordinate
    X_ATTR = _xLast
    Y_ATTR = _yLast
    -> tmpID_4
    -> Junction_7
    -> Junction_75
Note: tmpID_14 : Input
Junction_75
Note: tmpID_2 : Input
Junction_7
    -> Junction_53

Bookmark: set up quasi-2D crs
Rotator_13
    ANGLE = @Value(rightAngle)
    XORIG = @Value(_xFirst)
    YORIG = @Value(_yFirst)
    ROTATED -> CoordinateSwapper_10
Note: y to Z
CoordinateSwapper_10
    SWAP_TYPE = Y <-> Z
    -> 2DForcer
2DForcer
    2D -> Clipper_2 [CLIPPEE]

Bookmark: Building solid
Note: edited facade
Junction_33
    -> AttributeKeeper_6
Note: clean attributes
AttributeKeeper_6
    CREATE_BULK_MODE_FEATURES = NO
    KEEP_ATTRS = gml_parent_id,gml_id
    -> FaceReplacer
FaceReplacer
    ANGULAR_TOLERANCE_CHOICE = Ignore
    THICKNESS_TOLERANCE_CHOICE = Ignore
    -> GeometryValidator
Note: planarity check
GeometryValidator
    ISSUE_ATTR_NAME = _issues
    PRESETS = Custom
    REPAIR = Yes
    RULES = PLANAR_SURFACE CHECK_AREA]DO_CHECK_AREA]TOLERANCE_MODE]AUTO]TOLERANCE]<Unused>]ANGULAR_TOLERANCE_MODE]AUTO]ANGULAR_TOLERANCE]<Unused>]FME_CONTROLLER_QUERY_FILE]transformers\dependencies\geometryvalidator\PLANAR_SURFACE.fme
    SUMMARY = Detailed
    PASSED -> Junction_31
    FAILED -> Junction_31
    REPAIRED -> Junction_31
Junction_31
    -> Orientor
Orientor
    FLIP_APPEARANCES_CHOICE = Yes
    KIND = REVERSE
    ORIENTED -> AttributeKeeper_4
Note: clean attributes
AttributeKeeper_4
    CREATE_BULK_MODE_FEATURES = NO
    KEEP_ATTRS = gml_parent_id,gml_id
    -> Aggregator
Note: set multiSurface
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> CityGMLGeometrySetter_2
Note: set wall
CityGMLGeometrySetter_2
    GEOM = lod3MultiSurface
    ROLE = boundedBy
    -> CityGMLSemSetter_2

FME custom transformer BoundsFitter
Moves and scales the input feature so that its bounding box will be fit to the bounding box of another feature. If you set the Group By parameter, the fitting operation will be performed for sets of features grouped by the specified attributes.
    This transformer works with these two modes.
    2D
    : The transformer accepts both 2D and 3D features, but performs the fitting operation always in 2D. That is, the z-coordinate of any vertex will not be changed anyway in this mode. 
    3D
    : The transformer accepts 3D features only, and performs the fitting operation in 3D. If the input feature is 2D, it won't be processed/referenced and will be output via the NotCorrected/Unreferenced port.
    If the area of the bounding box is equal to 0 in 2D mode or the volume is equal to 0 in 3D mode, the feature (or the set of features when the Group By parameter is set) won't be processed/referenced and will be output via the NotCorrected/Unreferenced port.
    Naturally the feature that doesn't have a geometry will also be output via the NotCorrected/Unreferenced port.
Input Ports 
    Observed
    : 
    Input features which should be processed.
    Control
    : 
    Input features which should be referenced to assume a bounding box that will be used to perform the fitting operation. When the Group By parameter is not set, only the first Control feature will be referenced and others will be output via the Unreferenced port.
    Output Ports 
    Corrected
    : 
    Processed Observed features will be output via this port.
    NotCorrected
    : 
    Not processed Observed features will be output via this port.
    Referenced
    :
    Referenced Control features will be output via this port. 
    Unreferenced
    : 
    Unreferenced Control features will be output via this port.
    Parameters 
    Group By
    : 
    You can specify one or more feature attributes to this parameter to make sets of input features grouped by the specified attributes. The attribute names should be common to the Observed and Control features.
    When you set this parameter, this transformer considers the bounds of both Observed and Control features as the accumulated bounding box for each set. Then, the fitting operation will be performed between a set of Observed features and a set of Control features belonging to the same group.
    Observed Input is Ordered by Group
    :
    If you set the Group By parameter and also it is guaranteed that the Observed features will be input in the order for each group, you can set "Yes" to this parameter to increase the performance.
    Control Input is Ordered by Group
    : 
    If you set the Group By parameter and also it is guaranteed that the Control features will be input in the order for each group, you can set "Yes" to this parameter to increase the performance.
    Mode
    :
    Select one of these two modes. 
    2D
    : The transformer accepts both 2D and 3D features, but performs the fitting operation always in 2D. That is, the z-coordinate of any vertex will not be changed anyway in this mode.
    3D
    : The transformer accepts 3D features only, and performs the fitting operation in 3D. If the input feature is 2D, it won't be processed/referenced and will be output via the NotCorrected/Unreferenced port.

Parameters:
- GROUP_BY =   # " " Group By
- ORDERED = No   # Observed Input is Ordered by Group
- ORDERED_2 = No   # Control Input is Ordered by Group
- MODE = 2D   # Mode

Observed (input)
    -> GeometryFilter
Note: If the featurue doesn't have geometry or the geometry is 2D in 3D mode, it goes to NotCorrected/Unreferenced port.
GeometryFilter
    BREAK_AGG = No
    GEOM_PORT_NAMES = Null
    NULL -> Tester_9_FAILED
    <UNFILTERED> -> Tester_9
Tester_9
    BOOL_OP = COMPOSITE
    COMPOSITE_TEST = "1 OR (2 AND 3)"
    TEST_CLAUSE:
      TEST $(MODE) = 2D
      TEST $(MODE) = 3D
      TEST @Evaluate(@Dimension()) = 3
    TEST_MODE = Automatic
    PASSED -> Tester
    FAILED -> Tester_9_FAILED
Tester
    BOOL_OP = OR
    TEST_CLAUSE = TEST $(GROUP_BY) != ""
    TEST_MODE = Automatic
    PASSED -> Aggregator
    FAILED -> BoundsExtractor
Note: If the Group By parameter is set, perform aggregation of input features grouping by the attributes. The aggregate features will be de-aggregated before outputting.
Aggregator
    ACCUM_ATTRS_NAME = Drop Incoming Attributes
    AGGREGATE_TYPE = Heterogeneous Collection
    GROUP_BY = $(GROUP_BY)
    LIST_NAME = __bfitter.o_list
    MODE = Geometry - Assemble One Level
    ORDERED = $(ORDERED)
    SEP = ,
    AGGREGATE -> BoundsExtractor
BoundsExtractor
    XMAX = __bfitter.o_xmax
    XMIN = __bfitter.o_xmin
    YMAX = __bfitter.o_ymax
    YMIN = __bfitter.o_ymin
    ZMAX = __bfitter.o_zmax
    ZMIN = __bfitter.o_zmin
    -> Tester_2
Note: Failed features go to Tester_5.
Tester_2
    BOOL_OP = COMPOSITE
    COMPOSITE_TEST = "1 AND 2 AND (3 OR 4)"
    TEST_CLAUSE:
      TEST @Value(__bfitter.o_xmin) < @Value(__bfitter.o_xmax)
      TEST @Value(__bfitter.o_ymin) < @Value(__bfitter.o_ymax)
      TEST $(MODE) = 2D
      TEST @Value(__bfitter.o_zmin) < @Value(__bfitter.o_zmax)
    TEST_MODE = Automatic
    PASSED -> FeatureMerger [REQUESTOR]
    FAILED -> Tester_5
Note: Connected to NotCorrected port
Tester_9_FAILED: Junction
    -> NotCorrected (output)
Control (input)
    -> GeometryFilter_2
GeometryFilter_2
    BREAK_AGG = No
    GEOM_PORT_NAMES = Null
    NULL -> Tester_10_FAILED
    <UNFILTERED> -> Tester_10
Tester_10
    BOOL_OP = COMPOSITE
    COMPOSITE_TEST = "1 OR (2 AND 3)"
    TEST_CLAUSE:
      TEST $(MODE) = 2D
      TEST $(MODE) = 3D
      TEST @Evaluate(@Dimension()) = 3
    TEST_MODE = Automatic
    PASSED -> Tester_3
    FAILED -> Tester_10_FAILED
Tester_3
    BOOL_OP = OR
    TEST_CLAUSE = TEST $(GROUP_BY) != ""
    TEST_MODE = Automatic
    PASSED -> Aggregator_2
    FAILED -> BoundsExtractor_2
Aggregator_2
    ACCUM_ATTRS_NAME = Drop Incoming Attributes
    AGGREGATE_TYPE = Heterogeneous Collection
    GROUP_BY = $(GROUP_BY)
    LIST_NAME = __bfitter.c_list
    MODE = Geometry - Assemble One Level
    ORDERED = $(ORDERED_2)
    SEP = ,
    AGGREGATE -> BoundsExtractor_2
BoundsExtractor_2
    XMAX = __bfitter.c_xmax
    XMIN = __bfitter.c_xmin
    YMAX = __bfitter.c_ymax
    YMIN = __bfitter.c_ymin
    ZMAX = __bfitter.c_zmax
    ZMIN = __bfitter.c_zmin
    -> Tester_4
Tester_4
    BOOL_OP = COMPOSITE
    COMPOSITE_TEST = "1 AND 2 AND (3 OR 4)"
    TEST_CLAUSE:
      TEST @Value(__bfitter.c_xmin) < @Value(__bfitter.c_xmax)
      TEST @Value(__bfitter.c_ymin) < @Value(__bfitter.c_ymax)
      TEST $(MODE) = 2D
      TEST @Value(__bfitter.c_zmin) < @Value(__bfitter.c_zmax)
    TEST_MODE = Automatic
    PASSED -> FeatureMerger [SUPPLIER]
    FAILED -> Tester_4_FAILED_-__Tester_7
FeatureMerger
    ATTR_ACCUM_MODE = Merge Supplier
    ATTR_CONFLICT_RES = Use Requestor
    GROUP_BY = $(GROUP_BY)
    IGNORE_NULLS = No
    JOIN_KEYS = 1 1 AUTO
    MERGE_TYPE = Attributes Only
    PROCESS_DUPS = No
    REJECT_NULL_MISSING_KEYS = No
    SUPPLIERS_FIRST = No
    MERGED -> Tester_11
    NOT_MERGED -> FeatureMerger_NOT_MERGED_-__Tester_5
    REFERENCED -> AttributeRemover
    UNREFERENCED -> Tester_4_FAILED_-__Tester_7
    DUPLICATE_SUPPLIER -> Tester_4_FAILED_-__Tester_7
Tester_11
    BOOL_OP = OR
    TEST_CLAUSE = TEST $(MODE) = 2D
    TEST_MODE = Automatic
    PASSED -> Offsetter
    FAILED -> Offsetter_3
Note: Connected to Tester_5
FeatureMerger_NOT_MERGED_-__Tester_5: Junction
    -> Tester_5
Tester_5
    BOOL_OP = OR
    TEST_CLAUSE = TEST $(GROUP_BY) != ""
    TEST_MODE = Automatic
    PASSED -> AttributeExposer
    FAILED -> Tester_6
AttributeExposer
    ATTR_LIST = __bfitter.o_list{}
    -> Deaggregator
Deaggregator
    ATTR_ACCUM_MODE = Merge List Attributes
    ATTR_CONFLICT_RES = Use List Attribute Values
    EXPLODE_INSTANCES = No
    LIST_ATTR = __bfitter.o_list{}
    LIST_ATTR_MODE_LOOKUP = LEAN
    MODE = Flatten One Level
    SPLIT_COMPOSITES = No
    DEAGGREGATED -> Tester_6
Tester_6
    BOOL_OP = OR
    TEST_CLAUSE = TEST @Value(__bfitter.corrected) = 1
    TEST_MODE = Automatic
    PASSED -> BulkAttributeRemover
    FAILED -> BulkAttributeRemover_2
BulkAttributeRemover
    ATTR_EXP = ^__bfitter.+
    -> Corrected (output)
Corrected (output)
BulkAttributeRemover_2
    ATTR_EXP = ^__bfitter.+
    -> NotCorrected (output)
NotCorrected (output)
AttributeRemover
    REMOVE_ATTRS = numReferences
    -> Tester_7
Tester_4_FAILED_-__Tester_7: Junction
    -> Tester_7
Tester_7
    BOOL_OP = OR
    TEST_CLAUSE = TEST $(GROUP_BY) != ""
    TEST_MODE = Automatic
    PASSED -> AttributeExposer_2
    FAILED -> Tester_8
AttributeExposer_2
    ATTR_LIST = __bfitter.c_list{}
    -> Deaggregator_2
Deaggregator_2
    ATTR_ACCUM_MODE = Merge List Attributes
    ATTR_CONFLICT_RES = Use List Attribute Values
    EXPLODE_INSTANCES = No
    LIST_ATTR = __bfitter.c_list{}
    LIST_ATTR_MODE_LOOKUP = LEAN
    MODE = Flatten One Level
    SPLIT_COMPOSITES = No
    DEAGGREGATED -> Tester_8
Tester_8
    BOOL_OP = OR
    TEST_CLAUSE = TEST @Value(__bfitter.referenced) = 1
    TEST_MODE = Automatic
    PASSED -> BulkAttributeRemover_3
    FAILED -> BulkAttributeRemover_4
BulkAttributeRemover_3
    ATTR_EXP = ^__bfitter.+
    -> Referenced (output)
Referenced (output)
BulkAttributeRemover_4
    ATTR_EXP = ^__bfitter.+
    -> Unreferenced (output)
Note: Tester_2 and Tester_4 / If the area of the bounding box is equal to 0 in 2D mode or the volume is equal to 0 in 3D mode, the feature (or the set of features when the Group By parameter is set) won't be processed and will be output via the NotCorrected/Unreferenced port.
Note: Connected to Unreferenced port
Tester_10_FAILED: Junction
    -> Unreferenced (output)
Unreferenced (output)

Bookmark: Perform Fitting Operation (Move and Scale)
Note: The Offsetter+Scaler+Offsetter produces higher accuracy than the Affiner.
Offsetter
    MODE = Cartesian Coordinate
    XOFF = -@Value(__bfitter.o_xmin)
    YOFF = -@Value(__bfitter.o_ymin)
    ZOFF = 0
    OFFSET -> Scaler
Scaler
    RASTER_SCALING = Extents
    SCALE_ORIGIN = 0,0
    TEXT_LOC_ONLY = Location and Size
    XSCALE = (@Value(__bfitter.c_xmax)-@Value(__bfitter.c_xmin))/(@Value(__bfitter.o_xmax)-@Value(__bfitter.o_xmin))
    YSCALE = (@Value(__bfitter.c_ymax)-@Value(__bfitter.c_ymin))/(@Value(__bfitter.o_ymax)-@Value(__bfitter.o_ymin))
    ZSCALE = 1
    SCALED -> Offsetter_2
Offsetter_2
    MODE = Cartesian Coordinate
    XOFF = @Value(__bfitter.c_xmin)
    YOFF = @Value(__bfitter.c_ymin)
    ZOFF = 0
    OFFSET -> Tester_5
Offsetter_3
    MODE = Cartesian Coordinate
    XOFF = -@Value(__bfitter.o_xmin)
    YOFF = -@Value(__bfitter.o_ymin)
    ZOFF = -@Value(__bfitter.o_zmin)
    OFFSET -> Scaler_2
Scaler_2
    RASTER_SCALING = Extents
    SCALE_ORIGIN = 0,0
    TEXT_LOC_ONLY = Location and Size
    XSCALE = (@Value(__bfitter.c_xmax)-@Value(__bfitter.c_xmin))/(@Value(__bfitter.o_xmax)-@Value(__bfitter.o_xmin))
    YSCALE = (@Value(__bfitter.c_ymax)-@Value(__bfitter.c_ymin))/(@Value(__bfitter.o_ymax)-@Value(__bfitter.o_ymin))
    ZSCALE = (@Value(__bfitter.c_zmax)-@Value(__bfitter.c_zmin))/(@Value(__bfitter.o_zmax)-@Value(__bfitter.o_zmin))
    SCALED -> Offsetter_4
Offsetter_4
    MODE = Cartesian Coordinate
    XOFF = @Value(__bfitter.c_xmin)
    YOFF = @Value(__bfitter.c_ymin)
    ZOFF = @Value(__bfitter.c_zmin)
    OFFSET -> Tester_5
