FME workspace Extracting_shape_based_on_BayNet_output.fmw

Parameters:
- DestDataset_SHAPEFILE = D:\projects\PointCloud_Image_fusion\data\extractedShapes\wallAmofa   # Destination Esri Shapefile Folder
- SourceDataset_CITYGML = D:\projects\TUMbldExplore\datasets\raw\CityGML\TUM Munich\TUM Munich.gml   # Source CityGML File(s)
- bldSelect = DEBY_LOD2_4959323   # Select building ID
- SourceDataset_GEOTIFF_5 = D:\projects\PointCloud_Image_fusion\data\toBayNet\probabilityMapsOutBayNet\wallAmofa\openingProbabilityMap_Probability_opening.tif   # Source GeoTIFF File(s)

Readers:
- CITYGML_1: CITYGML from $(SourceDataset_CITYGML)
- GEOTIFF_1: GEOTIFF from $(SourceDataset_GEOTIFF_5)

Writers:
- SHAPEFILE_1: SHAPEFILE to $(DestDataset_SHAPEFILE)

Bookmark: 1 INPUT
GEOTIFF (reader GEOTIFF_1)
    -> Junction_4
Junction_4
    -> BoundingBoxAccumulator
    -> RasterToPolygonCoercer

Bookmark: raster to vector
RasterToPolygonCoercer
    EXTRACT_NODATA = No
    LABEL_ATTRIBUTE = _label
    PRESERVE_ATTRIBUTES = Yes
    POLYGONS -> TestFilter_2

Bookmark: probability threshold
TestFilter_2
    DEFAULT_VALUE = <UNFILTERED>
    TEST_LIST = "BOOL_OP,OR,COMPOSITE_TEST,""""""1"""""",TEST_CLAUSE,TEST @Value(_label) > 0.7",>0.7
    >0.7 -> Junction
Note: work on regions
Junction
    -> Dissolver
Note: avg scores
Dissolver
    ACCUM_INPUT_ATTRS = Use Attributes From One Feature
    CLEANING_TOLERANCE = Automatic
    CONNECT_Z_MODE = First Wins
    DEAGGREGATE_INPUT = Yes
    LIST_ATTRS_TO_INCLUDE = _label
    LIST_NAME = score
    WEIGHT = _label
    AREA -> Bufferer

Bookmark: connect touching polygons
Note: 0.01
Bufferer
    ANGLE = 22.5
    CAP_STYLE = Arc
    CORNER_STYLE = Arc
    MODE = AREA
    OFFSET = 0.01
    OFFSET_UNITS = NONE
    PRECISION = APPROX
    BUFFERED -> Dissolver_3
Dissolver_3
    ACCUM_INPUT_ATTRS = Use Attributes From One Feature
    CLEANING_TOLERANCE = Automatic
    CONNECT_Z_MODE = First Wins
    DEAGGREGATE_INPUT = Yes
    WEIGHT = _label
    AREA -> AreaCalculator_2

Bookmark: filter out small segments
AreaCalculator_2
    AREA_ATTR = _area
    AREA_TYPE = Plane Area
    MULT = 1
    -> Tester_2
Tester_2
    BOOL_OP = OR
    COMPOSITE_TEST = 1
    TEST_CLAUSE = TEST @Value(_area) > 2
    TEST_MODE = TEST
    PASSED -> Junction_2
Note: >2pix
Junction_2
    -> conflictID

Bookmark: add tmp ID to match conflicts
conflictID: Counter
    CNT_ATTR = conflictID
    DOMAIN = counter
    SCOPE = Local
    START = 0
    -> openingClassAssign_3
openingClassAssign_3: AttributeCreator
    ATTR_TABLE = SET_TO openingClass = RectangleWindow
    -> DonutHoleExtractor_3

Bookmark: hole threshold
Note: in case of donuts -> dissolve them
DonutHoleExtractor_3
    DEAGGREGATE_INPUT = Yes
    OUTERSHELL -> AreaCalculator_8
    HOLE -> AreaCalculator_7
AreaCalculator_8
    AREA_ATTR = shellArea
    AREA_TYPE = Plane Area
    MULT = 1
    -> FeatureMerger_20 [REQUESTOR]
AreaCalculator_7
    AREA_ATTR = holeArea
    AREA_TYPE = Plane Area
    MULT = 1
    -> Aggregator_11
Aggregator_11
    ACCUM_ATTRS_NAME = Use Attributes From One Feature
    AGGREGATE_TYPE = Homogeneous Collection (If Possible)
    GROUP_BY = conflictID
    MODE = Geometry - Assemble One Level
    SEP = ,
    SUM = holeArea
    AGGREGATE -> FeatureMerger_20 [SUPPLIER]
    AGGREGATE -> Aggregator_11_Aggregate
FeatureMerger_20
    ATTR_ACCUM_MODE = Merge Supplier
    ATTR_CONFLICT_RES = Use Requestor
    IGNORE_NULLS = No
    JOIN_KEYS = @Value(conflictID) @Value(conflictID) AUTO
    MERGE_TYPE = Attributes Only
    PROCESS_DUPS = NO
    REJECT_NULL_MISSING_KEYS = No
    SUPPLIERS_FIRST = No
    MERGED -> AttributeCreator_4
    UNMERGED_REQUESTOR -> AttributeCreator_4
AttributeCreator_4
    ATTR_TABLE:
      SET_TO holeThreshold = 0.2
      SET_TO holeRatio = @div(@Value(holeArea),@Value(shellArea))
    -> Tester_12
Tester_12
    BOOL_OP = OR
    COMPOSITE_TEST = 1
    TEST_CLAUSE = TEST @Value(holeThreshold) > @Value(holeRatio)
    TEST_MODE = TEST
    PASSED -> Generalizer
Note: remove double-vertices
Generalizer
    ALG_TEXT = Douglas (Generalize)
    PRESERVE = No
    PRESERVE_PATHS = No
    TOLERANCE = 0.1
    -> operator_size
Aggregator_11_Aggregate: Inspector

Bookmark: morphological, opening + closing
Note: alternative: directly operate on image using RasterConvolver with erosion and dilation functions
operator_size: AttributeCreator
    ATTR_TABLE:
      SET_TO operator_size = 1
      SET_TO negative_operator_size = -1
    -> erosion_2
Note: opening followed by closing
Junction_3
    -> Deaggregator_7

Bookmark: opening
erosion_2: Bufferer
    ANGLE = 22.5
    CAP_STYLE = Arc
    CORNER_STYLE = Arc
    MODE = AREA
    OFFSET = @Value(negative_operator_size)
    OFFSET_UNITS = NONE
    PRECISION = APPROX
    BUFFERED -> GeometryFilter_2
GeometryFilter_2
    BREAK_AGG = No
    GEOM_PORT_NAMES = Null
    <UNFILTERED> -> dilation_3
dilation_3: Bufferer
    ANGLE = 22.5
    CAP_STYLE = Arc
    CORNER_STYLE = Arc
    MODE = AREA
    OFFSET = @Value(operator_size)
    OFFSET_UNITS = NONE
    PRECISION = APPROX
    BUFFERED -> dilation_2
    BUFFERED -> opening
opening: Inspector [off]

Bookmark: closing
dilation_2: Bufferer
    ANGLE = 22.5
    CAP_STYLE = Arc
    CORNER_STYLE = Arc
    MODE = AREA
    OFFSET = @Value(operator_size)
    OFFSET_UNITS = NONE
    PRECISION = APPROX
    BUFFERED -> GeometryFilter_3
GeometryFilter_3
    BREAK_AGG = No
    GEOM_PORT_NAMES = Null
    <UNFILTERED> -> erosion_3
erosion_3: Bufferer
    ANGLE = 22.5
    CAP_STYLE = Arc
    CORNER_STYLE = Arc
    MODE = AREA
    OFFSET = @Value(negative_operator_size)
    OFFSET_UNITS = NONE
    PRECISION = APPROX
    BUFFERED -> Junction_3
    BUFFERED -> closing
closing: Inspector [off]

Bookmark: reject small parts
Note: deagregate spatially disjointed parts
Deaggregator_7
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AreaCalculator_6
AreaCalculator_6
    AREA_ATTR = _areaVer2
    AREA_TYPE = Plane Area
    MULT = 1
    -> Tester_11
Note: >x
Tester_11
    BOOL_OP = OR
    COMPOSITE_TEST = 1
    TEST_CLAUSE = TEST @Value(_areaVer2) > 36
    TEST_MODE = TEST
    PASSED -> openingID
openingID: Counter
    CNT_ATTR = openingID
    DOMAIN = counter
    SCOPE = Local
    START = 0
    -> BoundingBoxReplacer_3
    -> FeatureMerger_21 [REQUESTOR]

Bookmark: elongation index
BoundingBoxReplacer_3
    BOXTYPE = 2D Bounding Box
    BOX -> AreaCalculator_9
Note: index ratio, b/a
AttributeCreator_6
    ATTR_TABLE = SET_TO elongationRatioBtoA = @div(@Value(bLineLength),@Value(aLineLength))
    -> AttributeCreator_8
Note: index ratio, b/a
AttributeCreator_8
    ATTR_TABLE = SET_TO elongationRatioAtoB = @div(@Value(aLineLength),@Value(bLineLength))
    -> Tester_14
Note: index treshold
Tester_14
    BOOL_OP = COMPOSITE
    COMPOSITE_TEST = 1 AND 2
    TEST_CLAUSE:
      TEST @Value(elongationRatioBtoA) > 0.15
      TEST @Value(elongationRatioAtoB) > 0.39
    TEST_MODE = TEST
    PASSED -> GeometryRemover_4
GeometryRemover_4
    -> FeatureMerger_21 [SUPPLIER]

Bookmark: select lowest and highest lines
AreaCalculator_9
    AREA_ATTR = AtoCalcb
    AREA_TYPE = Plane Area
    MULT = 1
    -> BoundsExtractor_8
Note: bbox H
BoundsExtractor_8
    YMAX = maxBBOXh
    YMIN = minBBOXh
    -> GeometryPartExtractor_3
GeometryPartExtractor_3
    GQUERY:
      for $geom in //geometry
      where $geom/@fme_geometry_type = 'IFMELine'
      return number($geom/@fme_id)
    EXTRACTED -> Chopper_3
Chopper_3
    DEAGGREGATE_INPUT = Deaggregate
    MAX_VERTICES = 2
    MODE = By Vertex
    REMNANT_ATTR = _remnant
    CHOPPED -> BoundsExtractor_10
Note: lines H
BoundsExtractor_10
    YMAX = lineHmax
    -> Tester_13
Note: select lowest line
Tester_13
    BOOL_OP = OR
    COMPOSITE_TEST = 1
    TEST_CLAUSE = TEST @Value(lineHmax) = @Value(minBBOXh)
    TEST_MODE = TEST
    PASSED -> LengthCalculator
Note: calculate a
LengthCalculator
    DIM = 2
    LEN_ATTR = aLineLength
    MULT = 1
    -> AttributeCreator_5
Note: a * b = area so area/a = b
AttributeCreator_5
    ATTR_TABLE = SET_TO bLineLength = @div(@Value(AtoCalcb),@Value(aLineLength))
    -> AttributeCreator_6

Bookmark: 2 SYSTEM
Note: merge and filter only these fulfiling elongation index measure
FeatureMerger_21
    ATTR_ACCUM_MODE = Merge Supplier
    ATTR_CONFLICT_RES = Use Requestor
    IGNORE_NULLS = No
    JOIN_KEYS = @Value(openingID) @Value(openingID) AUTO
    MERGE_TYPE = Attributes Only
    PROCESS_DUPS = NO
    REJECT_NULL_MISSING_KEYS = No
    SUPPLIERS_FIRST = No
    MERGED -> AttributeRenamer
AttributeRenamer
    ATTR_TABLE = RENAME_SET_DEFAULT _label > conf_score
    -> AttributeKeeper_12
Note: clean attributes
AttributeKeeper_12
    CREATE_BULK_MODE_FEATURES = NO
    KEEP_ATTRS = openingClass,openingID,conflictID,conf_score,aLineLength,bLineLength
    -> tmpID_7
Note: clean attributes
AttributeKeeper_2
    CREATE_BULK_MODE_FEATURES = NO
    KEEP_ATTRS = openingClass,openingID,conflictID,conf_score,aLineLength,bLineLength
    -> extractedShapesProbVectorMap (writer SHAPEFILE_1)

Bookmark: scaler
tmpID_7: AttributeCreator
    ATTR_TABLE = SET_TO tmpID = 1
    -> FeatureMerger_3 [REQUESTOR]
FeatureMerger_3
    ATTR_ACCUM_MODE = Merge Supplier
    ATTR_CONFLICT_RES = Use Requestor
    IGNORE_NULLS = No
    JOIN_KEYS = @Value(tmpID) @Value(tmpID) AUTO
    MERGE_TYPE = Attributes Only
    PROCESS_DUPS = NO
    REJECT_NULL_MISSING_KEYS = No
    SUPPLIERS_FIRST = No
    MERGED -> Scaler
Scaler
    RASTER_SCALING = Extents
    SCALE_ORIGIN = 0,0
    TEXT_LOC_ONLY = Location and Size
    XSCALE = @Value(scaleX)
    YSCALE = @Value(scaleY)
    ZSCALE = 1
    SCALED -> Clipper [CLIPPER]
Scaler_2
    RASTER_SCALING = Extents
    SCALE_ORIGIN = 0,0
    TEXT_LOC_ONLY = Location and Size
    XSCALE = @Value(scaleX)
    YSCALE = @Value(scaleY)
    ZSCALE = 1
    SCALED -> Clipper [CLIPPEE]
Note: add background
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> AttributeKeeper_2
    OUTSIDE -> AttributeCreator
AttributeCreator
    ATTR_TABLE = SET_TO conf_score = 0
    -> AttributeKeeper_2

Bookmark: input raster dim
BoundingBoxAccumulator
    ACCUM_ATTRS_NAME = Use Attributes From One Feature
    BOUNDING_BOX -> BoundsExtractor
Note: in this case max is the raster dim
BoundsExtractor
    XMAX = _xmax
    YMAX = _ymax
    -> AttributeRenamer_2

Bookmark: scaling factor
AttributeRenamer_2
    ATTR_TABLE:
      RENAME_SET_DEFAULT _xmax > a_raster
      RENAME_SET_DEFAULT _ymax > b_raster
    -> tmpID_3
tmpID_3: AttributeCreator
    ATTR_TABLE = SET_TO tmpID = 1
    -> FeatureMerger_2 [REQUESTOR]
AttributeRenamer_3
    ATTR_TABLE:
      RENAME_SET_DEFAULT aLineLength > a_facade
      RENAME_SET_DEFAULT bLineLength > b_facade
    -> tmpID_6
tmpID_6: AttributeCreator
    ATTR_TABLE = SET_TO tmpID = 1
    -> FeatureMerger_2 [SUPPLIER]
FeatureMerger_2
    ATTR_ACCUM_MODE = Merge Supplier
    ATTR_CONFLICT_RES = Use Requestor
    IGNORE_NULLS = No
    JOIN_KEYS = @Value(tmpID) @Value(tmpID) AUTO
    MERGE_TYPE = Attributes Only
    PROCESS_DUPS = NO
    REJECT_NULL_MISSING_KEYS = No
    SUPPLIERS_FIRST = No
    MERGED -> scaleFactorEstimate
scaleFactorEstimate: AttributeCreator
    ATTR_TABLE:
      SET_TO scaleX = @div(@Value(a_facade),@Value(a_raster))
      SET_TO scaleY = @div(@Value(b_facade),@Value(b_raster))
    -> FeatureMerger_3 [SUPPLIER]
    -> Scaler_2

Bookmark: given city model
Address (reader CITYGML_1)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, DatenquelleBodenhoehe xml_buffer, DatenquelleDachhoehe xml_buffer, DatenquelleLage xml_buffer, GE_LoD2_zOffset xml_buffer, Gemeindeschluessel xml_buffer, HoeheDach xml_buffer, HoeheGrund xml_buffer, Methode xml_buffer, NiedrigsteTraufeDesGebaeudes xml_buffer, Qualitaet xml_buffer, StandLK xml_buffer
    -> Reprojector
CityModel (reader CITYGML_1)
    attributes: citygml_target_uri xml_buffer, gml_description xml_buffer, gml_name xml_buffer, citygml_city_object_member{}.xlink_href xml_buffer, gml_feature_member{}.xlink_href xml_buffer
GroundSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Reprojector
RoofSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Dachneigung xml_buffer, Dachorientierung xml_buffer, Flaeche xml_buffer, Z_MAX xml_buffer, Z_MAX_ASL xml_buffer, Z_MIN xml_buffer, Z_MIN_ASL xml_buffer
    -> Reprojector
WallSurface (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_level_of_detail{} xml_buffer, citygml_opening{}.xlink_href xml_buffer, Flaeche xml_buffer, Z_MAX xml_buffer, Z_MAX_ASL xml_buffer, Z_MIN xml_buffer, Z_MIN_ASL xml_buffer
    -> Reprojector

Bookmark: pick the building
Note: to ETRS89
Reprojector
    DEST = ETRS89.UTM-32N
    INTERPOLATION_TYPE_NAME = Nearest Neighbor
    RASTER_CELL_SIZE = Preserve Cells
    RASTER_TOLERANCE = 0.0
    SOURCE = Read from feature
    REPROJECTED -> Decider_3
Decider_3: TestFilter
    DEFAULT_VALUE = <UNFILTERED>
    TEST_LIST:
      "BOOL_OP,OR,COMPOSITE_TEST,""""""1 OR 2"""""",TEST_CLAUSE,TEST @Value(gml_id) = $(bldSelect)
      TEST @Value(gml_parent_id) = $(bldSelect)",$(bldSelect)
    $(bldSelect) -> Split2parts
Split2parts: TestFilter
    DEFAULT_VALUE = <UNFILTERED>
    TEST_LIST = "BOOL_OP,OR,COMPOSITE_TEST,""""""1"""""",TEST_CLAUSE,TEST @Value(fme_feature_type) = GroundSurface",GroundSurface,"BOOL_OP,OR,COMPOSITE_TEST,""""""1"""""",TEST_CLAUSE,TEST @Value(fme_feature_type) = WallSurface",WallSurface,"BOOL_OP,OR,COMPOSITE_TEST,""""""1"""""",TEST_CLAUSE,TEST @Value(fme_feature_type) = Building",Building,"BOOL_OP,OR,COMPOSITE_TEST,""""""1"""""",TEST_CLAUSE,TEST @Value(fme_feature_type) = RoofSurface",Roof
    WallSurface -> TestFilter_11

Bookmark: cut within the facade range
Note: facade of interest
TestFilter_11
    DEFAULT_VALUE = <UNFILTERED>
    TEST_LIST = "BOOL_OP,OR,COMPOSITE_TEST,""""""1"""""",TEST_CLAUSE,TEST @Value(gml_id) = DEBY_LOD2_4959323_5150f87d-bb94-4ffe-bdac-c5d180e863d5",DEBY_LOD2_4959323_5150f87d-bb94-4ffe-bdac-c5d180e863d5
    DEBY_LOD2_4959323_5150f87d-bb94-4ffe-bdac-c5d180e863d5 -> Aggregator_6
Aggregator_6
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> 2DForcer_2
    AGGREGATE -> BoundsExtractor_6
    AGGREGATE -> tmpID_5
2DForcer_2

Bookmark: Select lowest line of the facade and calculate orientation and XYZ position
BoundsExtractor_6
    ZMAX = maxHeight
    ZMIN = minHeight
    -> Deaggregator_3
Deaggregator_3
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = Yes
    DEAGGREGATED -> GeometryPartExtractor_2
GeometryPartExtractor_2
    GQUERY:
      for $geom in //geometry
      where $geom/@fme_geometry_type = 'IFMELine'
      return number($geom/@fme_id)
    EXTRACTED -> Chopper_2
Chopper_2
    DEAGGREGATE_INPUT = Deaggregate
    MAX_VERTICES = 2
    MODE = By Vertex
    REMNANT_ATTR = _remnant
    CHOPPED -> BoundsExtractor_5
Note: select lowest line
BoundsExtractor_5
    ZMAX = LineH
    -> TestFilter_6
TestFilter_6
    DEFAULT_VALUE = <UNFILTERED>
    TEST_LIST:
      "BOOL_OP,AND,COMPOSITE_TEST,""""""1 AND 2"""""",TEST_CLAUSE,TEST @Value(LineH) >= @sub(@Value(minHeight),0.5)
      TEST @Value(LineH) <= @sum(@Value(minHeight),0.5)",lowestLine
    lowestLine -> 2DForcer_5
2DForcer_5
    2D -> LineCombiner
LineCombiner
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> HorizontalAngleCalculator_3

Bookmark: angle and reference coordinates extract
Note: angle
HorizontalAngleCalculator_3
    ANGLE_TYPE = Feature
    UNIT_OUTPUT = DEG
    -> CoordinateExtractor
Note: first
CoordinateExtractor
    IND = 0
    MODE = Specify Coordinate
    X_ATTR = _xFirst
    Y_ATTR = _yFirst
    -> CoordinateExtractor_2
Note: last
CoordinateExtractor_2
    IND = -1
    MODE = Specify Coordinate
    X_ATTR = _xLast
    Y_ATTR = _yLast
    -> tmpID_4
    -> Junction_7
Note: tmpID_2 : Input
Junction_7
    -> Junction_53
Note: tmpID_6 : Input
Junction_53

Bookmark: Find correct 2D projection, angle alignment
tmpID_4: Counter
    CNT_ATTR = _count
    DOMAIN = counter
    SCOPE = Local
    START = 0
    -> FeatureMerger_6 [SUPPLIER]
tmpID_5: Counter
    CNT_ATTR = _count
    DOMAIN = counter
    SCOPE = Local
    START = 0
    -> FeatureMerger_6 [REQUESTOR]
FeatureMerger_6
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> ExpressionEvaluator_6
Note: obtain correct angle
ExpressionEvaluator_6
    ACTION = Create New Attribute
    EXPRESSION = @sub(360,@Value(_angle))
    VAL_ATTR = rightAngle
    -> Rotator_2

Bookmark: Facade rasterization
Rotator_2
    ANGLE = @Value(rightAngle)
    XORIG = @Value(_xFirst)
    YORIG = @Value(_yFirst)
    ROTATED -> CoordinateSwapper_2
Note: y to Z
CoordinateSwapper_2
    SWAP_TYPE = Y <-> Z
    -> AreaCalculator_3

Bookmark: calculate a and b of facade
AreaCalculator_3
    AREA_ATTR = AtoCalcb
    AREA_TYPE = Plane Area
    MULT = 1
    -> BoundsExtractor_2
Note: bbox H
BoundsExtractor_2
    YMAX = maxBBOXh
    YMIN = minBBOXh
    -> GeometryPartExtractor_4
GeometryPartExtractor_4
    GQUERY:
      for $geom in //geometry
      where $geom/@fme_geometry_type = 'IFMELine'
      return number($geom/@fme_id)
    EXTRACTED -> Chopper_4
Chopper_4
    DEAGGREGATE_INPUT = Deaggregate
    MAX_VERTICES = 2
    MODE = By Vertex
    REMNANT_ATTR = _remnant
    CHOPPED -> BoundsExtractor_3
Note: lines H
BoundsExtractor_3
    YMAX = lineHmax
    -> Tester_3
Note: select lowest line
Tester_3
    BOOL_OP = OR
    COMPOSITE_TEST = 1
    TEST_CLAUSE = TEST @Value(lineHmax) = @Value(minBBOXh)
    TEST_MODE = TEST
    PASSED -> LineCombiner_2
Note: just in case there are two/or more parts of the same line
LineCombiner_2
    ACCUM_ATTRS_NAME = Use Attributes From One Feature
    BREAK = no
    CONNECT_Z_MODE = First Wins
    CONSIDER_NODE_ELEVATION = no
    DEAGGREGATE_GEOMETRY = Deaggregate
    DIRECTION_NAME = direction
    JUNCTIONS_IGNORE_ATTRIBUTES = No
    LINES_AS_SEGMENTS = No
    PRESERVE = no
    TOPOLOGY = End noded
    LINE -> LengthCalculator_2
Note: calculate a
LengthCalculator_2
    DIM = 2
    LEN_ATTR = aLineLength
    MULT = 1
    -> AttributeCreator_2
Note: a * b = area so area/a = b
AttributeCreator_2
    ATTR_TABLE = SET_TO bLineLength = @div(@Value(AtoCalcb),@Value(aLineLength))
    -> AttributeRenamer_3

Bookmark: 3 OUTPUT
extractedShapesProbVectorMap (writer SHAPEFILE_1)
    attributes: conf_score char(200), openingCla char(200), conflictID number(20,0), openingID number(20,0), bLineLengt char(200), aLineLengt double
